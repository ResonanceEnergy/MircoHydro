# --- bootstrap: allow stand-alone run (load params.json if PARAMS not injected) ---
import os, json
if 'PARAMS' not in globals():
    HERE = os.path.dirname(__file__)
    ROOT = os.path.abspath(os.path.join(HERE, '..'))
    PARAMS_FILE = os.path.join(ROOT, 'params.json')
    if not os.path.exists(PARAMS_FILE):
        raise FileNotFoundError("params.json not found at: " + PARAMS_FILE)
    with open(PARAMS_FILE, 'r') as _f:
        PARAMS = json.load(_f)


# -*- coding: utf-8 -*-
import FreeCAD, Part
from FreeCAD import Vector

PV = PARAMS['VanePack_Common']
Angles = PARAMS['VanePacks']['Angles']
OD = float(PV['Outer_Diameter'])
ID = float(PV['Inner_Hub_D'])
Ht = float(PV['Height'])
t  = float(PV['Vane_Thickness'])
count = int(PV['Vane_Count'])

for ang in Angles:
    doc = FreeCAD.newDocument('VanePack_{}deg_vA1'.format(int(ang)))
    p1 = Vector(ID/2, 0, 0)
    p2 = Vector(OD/2, 0, 0)
    p3 = Vector(OD/2, t, 0)
    p4 = Vector(ID/2, t, 0)
    wire = Part.makePolygon([p1,p2,p3,p4,p1])
    face = Part.Face(wire)
    vane = face.extrude(Vector(0,0,Ht))
    vane.rotate(Vector(0,0,0), Vector(0,0,1), ang)
    vanes=[]
    for i in range(count):
        vcopy = vane.copy()
        vcopy.rotate(Vector(0,0,0), Vector(0,0,1), i*(360/count))
        vanes.append(vcopy)
    cmpd = Part.makeCompound(vanes)
    obj = doc.addObject('Part::Feature', 'VanePack_{}deg_vA1'.format(int(ang)))
    obj.Shape = cmpd
    doc.recompute()
