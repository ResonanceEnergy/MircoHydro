# -*- coding: utf-8 -*-
import FreeCAD, Part
from FreeCAD import Vector
import math

P = PARAMS['RetainerCap']
OD = float(P['OD'])
Thk = float(P['Thickness'])
PCD = float(P['Bolt_PCD'])
BCnt = int(P['Bolt_Count'])
CHole = float(P['Center_Hole'])

doc = FreeCAD.newDocument('Retainer_vA1')

r = OD/2
disk = Part.makeCylinder(r, Thk)
cyl = Part.makeCylinder(CHole/2, Thk+1)
ret = disk.cut(cyl)

for i in range(BCnt):
    ang = math.radians(i*(360/BCnt))
    x = (PCD/2)*math.cos(ang)
    y = (PCD/2)*math.sin(ang)
    bolt = Part.makeCylinder(3, Thk+1, Vector(x,y,0))
    ret = ret.cut(bolt)

obj = doc.addObject('Part::Feature', 'Retainer_vA1')
obj.Shape = ret
doc.recompute()
